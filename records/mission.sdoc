[DOCUMENT]
TITLE: Mission Records

[GRAMMAR]
IMPORT_FROM_FILE: @program

[MISSION_RECORD]
UID: TVC-MO-001
RECORD_TYPE: Objective
TITLE: Maintain Powered Attitude
SUBTEAM_OWNER: Systems
INDIVIDUAL_OWNER: Systems Lead
VEHICLE_CONFIGURATION: TVC-F1
MISSION_PHASE: Powered Ascent
FLIGHT_ATTEMPT: Flight 1
OPEN_ITEM_STATUS: None
STATUS: Draft
STATEMENT: Demonstrate that the vehicle can maintain attitude under nominal launch conditions.
RATIONALE: This mission objective demonstrates the program goal of thrust-vector control during powered ascent.

[MISSION_RECORD]
UID: TVC-MO-002
RECORD_TYPE: Objective
TITLE: Respond to Environmental Factors
SUBTEAM_OWNER: Systems
INDIVIDUAL_OWNER: Systems Lead
VEHICLE_CONFIGURATION: TVC-F1
MISSION_PHASE: Powered Ascent
FLIGHT_ATTEMPT: Flight 1
OPEN_ITEM_STATUS: None
STATUS: Draft
STATEMENT: Demonstrate that the vehicle can maintain attitude in response to reasonable environmental factors, such as wind gusts. Other environmental factors include temperature, humidity, and pressure.
RATIONALE: This mission objective demonstrates the program goal of thrust-vector control, even in response to expected environmental factors. Reasonable is based on the average expected conditions at the launch site. For example, a reasonable wind condition would be the average maximum gust over the course of a week.

[MISSION_RECORD]
UID: TVC-MO-003
RECORD_TYPE: Objective
TITLE: Capture Social Media Ready Content
SUBTEAM_OWNER: Systems
INDIVIDUAL_OWNER: Systems Lead
VEHICLE_CONFIGURATION: All
MISSION_PHASE: All
FLIGHT_ATTEMPT: All
OPEN_ITEM_STATUS: None
STATUS: Draft
STATEMENT: Achieve social media ready video capture of all launch phases defined in program configuration, with at least two angles of launch.
RATIONALE: This mission objective supports the overall GNC mission of recruiting and training members for the future, with high-quality social media content an integral part of doing so.

[MISSION_RECORD]
UID: TVC-MO-004
RECORD_TYPE: Objective
TITLE: Rapid Launch Turnaround
SUBTEAM_OWNER: Systems
INDIVIDUAL_OWNER: Systems Lead
VEHICLE_CONFIGURATION: All
MISSION_PHASE: All
FLIGHT_ATTEMPT: All
OPEN_ITEM_STATUS: None
STATUS: Draft
STATEMENT: Achieve a rapid rocket launch turnaround capability, allowing for 3+ launches per launch day, excluding time dedicated to unplanned hardware repairs, unplanned software configuration errors (such as large bias than expected), and other unplanned system failures.
RATIONALE: This mission objective supports the overall GNC mission of rapid launch, reusability, iteration, and testing by allowing for multiple launches each launch day.

[MISSION_RECORD]
UID: TVC-MO-005
RECORD_TYPE: Objective
TITLE: Capture Flight Data
SUBTEAM_OWNER: Systems, Electrical, Software
INDIVIDUAL_OWNER: Systems Lead
VEHICLE_CONFIGURATION: TVC-F1
MISSION_PHASE: All
FLIGHT_ATTEMPT: Flight 1
OPEN_ITEM_STATUS: None
STATUS: Draft
STATEMENT: Achieve data capture of all important flight parameters, including but not limited to raw sensor output, state estimation data, and state machine status.
RATIONALE: This mission objective supports GNC's goal of iteration by providing data for flight analysis and iteration.

[MISSION_RECORD]
UID: TVC-MO-006
RECORD_TYPE: Objective
TITLE: Recover Vehicle Safely
SUBTEAM_OWNER: Systems, Structures, Electrical, Software
INDIVIDUAL_OWNER: Systems Lead
VEHICLE_CONFIGURATION: TVC-F1
MISSION_PHASE: Parachute Descent
FLIGHT_ATTEMPT: Flight 1
OPEN_ITEM_STATUS: None
STATUS: Draft
STATEMENT: Achieve a soft landing of the rocket under parachute with nominal mission parameters.
RATIONALE: This mission objective supports GNC's goal of rapid launch and reusability, along with preservation of data, and limitation of resources used.

[MISSION_RECORD]
UID: TVC-MO-007
RECORD_TYPE: Objective
TITLE: Vehicle Structural Integrity
SUBTEAM_OWNER: Structures
INDIVIDUAL_OWNER: Structures Lead
VEHICLE_CONFIGURATION: TVC-F1
MISSION_PHASE: All
FLIGHT_ATTEMPT: Flight 1
OPEN_ITEM_STATUS: None
STATUS: Draft
STATEMENT: Demonstrate that the vehicle can sustain all loads without structural damage or disassembly, under conditions from all mission phases. This includes any loads as the rocket impacts the ground during recovery.
RATIONALE: This mission objective supports GNC's goal of rapid launch and reusability, along with reducing program costs by allowing components to be reused.

[MISSION_RECORD]
UID: TVC-MC-001
RECORD_TYPE: Constraint
TITLE: Vehicle Altitude Condition
SUBTEAM_OWNER: Systems
INDIVIDUAL_OWNER: Systems Lead
VEHICLE_CONFIGURATION: TVC-F1
MISSION_PHASE: All
FLIGHT_ATTEMPT: All
OPEN_ITEM_STATUS: None
STATUS: Draft
STATEMENT: The vehicle shall comply with launch site regulations that the rocket must get off the ground and shall not hit the ground while under motor power.
RATIONALE: This mission constraint ensures that the rocket parameters will allow it to actually get off the ground and stay in the air for the full extent of the motor burn, assuming the controls system keeps the rocket vertical.

[MISSION_RECORD]
UID: TVC-MO-008
RECORD_TYPE: Objective
TITLE: Controls Shutoff Condition
SUBTEAM_OWNER: Controls
INDIVIDUAL_OWNER: Controls Lead
VEHICLE_CONFIGURATION: TVC-F1
MISSION_PHASE: All
FLIGHT_ATTEMPT: All
OPEN_ITEM_STATUS: None
STATUS: Draft
STATEMENT: Demonstrate that the vehicle can shut off controls when determined that the rocket attitude can not be recovered. Shutting off controls is defined as actuating the gimbal to its known 0 position, then cutting power to the gimbal actuators.
RATIONALE: This mission objective ensures that the rocket does not try to control attitude at a point when it can no longer do so, and it may be unsafe to continue attempting to do so. Lower level requirement more clearly defines the conditions where rocket attitude can not be recovered.

[MISSION_RECORD]
UID: TVC-MO-009
RECORD_TYPE: Objective
TITLE: Closed Loop Controls
SUBTEAM_OWNER: Controls
INDIVIDUAL_OWNER: Controls Lead
VEHICLE_CONFIGURATION: TVC-F1
MISSION_PHASE: All
FLIGHT_ATTEMPT: All
OPEN_ITEM_STATUS: None
STATUS: Draft
STATEMENT: Demonstrate that the vehicle can use closed loop controls to control the rocket attitude under power.
RATIONALE: This mission objective is fundamental to GNCs mission of using active controls.

[MISSION_RECORD]
UID: TVC-MO-010
RECORD_TYPE: Objective
TITLE: Onboard state machine
SUBTEAM_OWNER: Controls
INDIVIDUAL_OWNER: Controls Lead
VEHICLE_CONFIGURATION: TVC-F1
MISSION_PHASE: All
FLIGHT_ATTEMPT: All
OPEN_ITEM_STATUS: None
STATUS: Draft
STATEMENT: Demonstrate that the vehicle software uses a state machine, with clearly defined state transitions and no undefined states, for all flight conditions.
RATIONALE: A state machine is essential to providing clear activities for each phase of the mission, helping to avoid things such as large if-else statements, among other things.

[MISSION_RECORD]
UID: TVC-MC-002
RECORD_TYPE: Constraint
TITLE: NAR Material Standards
SUBTEAM_OWNER: Systems
INDIVIDUAL_OWNER: Systems Lead
VEHICLE_CONFIGURATION: TVC-F1
MISSION_PHASE: All
FLIGHT_ATTEMPT: All
OPEN_ITEM_STATUS: None
STATUS: Draft
STATEMENT: The vehicle shall comply with NAR model rocket safety code (https://www.nar.org/ModelRocketSafetyCode). The vehicle shall not use any metal in the rocket externals.
RATIONALE: GNC launches at NAR launch sites, generally, and it is preferred to comply with as many standards as reasonable. One of these is materials, which should also be a reasonable constraint to meet.

[MISSION_RECORD]
UID: TVC-MC-003
RECORD_TYPE: Constraint
TITLE: Range Safety Analysis
SUBTEAM_OWNER: Systems
INDIVIDUAL_OWNER: Systems Lead
VEHICLE_CONFIGURATION: TVC-F1
MISSION_PHASE: All
FLIGHT_ATTEMPT: All
OPEN_ITEM_STATUS: TBD
RESOLUTION_OWNER: Controls Leads
RESOLUTION_PLAN: Controls should use a completed GNCSim architecture to simulate the exact launch range. TVC-REQ-030 has a clearer resolution plan that should be referenced.
RESOLUTION_DUE_DATE: September 30th
STATUS: Draft
STATEMENT: The mission shall use simulation for establishing a maximum [TBD_LaunchRange] area based on maxumum predicted launch dispersion of the rocket.
RATIONALE: GNC is dedicated to maintaing safe launches, and it is imperative that during launch a safe range is established.

[MISSION_RECORD]
UID: TVC-MO-011
RECORD_TYPE: Objective
TITLE: Removing launch rail
SUBTEAM_OWNER: Systems
INDIVIDUAL_OWNER: Systems Lead
VEHICLE_CONFIGURATION: TVC-F1
MISSION_PHASE: All
FLIGHT_ATTEMPT: Flights 4+
OPEN_ITEM_STATUS: None
STATUS: Draft
STATEMENT: Demonstrate that the vehicle can nominally launch under no-rail conditions.
RATIONALE: In order to truly demonstrate stabilized flight, the first phase of flight, takeoff, should be done without a launch rail. This requirement is limited to later flights as historically GNC has struggled more with takeoff from the pad.

[MISSION_RECORD]
UID: TVC-MO-012
RECORD_TYPE: Objective
TITLE: Protection against accidents
SUBTEAM_OWNER: Systems
INDIVIDUAL_OWNER: Systems Lead
VEHICLE_CONFIGURATION: TVC-F1
MISSION_PHASE: Pre-Launch
FLIGHT_ATTEMPT: All
OPEN_ITEM_STATUS: None
STATUS: Draft
STATEMENT: Demonstrate that the vehicle can operate under the conditions of common, low-level mistakes that have been made, including (but not limited to), dropping components/the entire vehicle, mistakes when plugging in wires, mistakes made in last minute changes, and forgetting smaller components.
RATIONALE: The team makes mistakes all the time. We accidentally plug in a wrong battery, we drop items, we forget something at home. It is worth it to consider these common mistakes, and, if easy solutions exist, implement these solutions to give us a better chance of insulating the launch against mistakes.

[MISSION_RECORD]
UID: TVC-MO-013
RECORD_TYPE: Objective
TITLE: Control Initial Delay
SUBTEAM_OWNER: Software
INDIVIDUAL_OWNER: Software Lead
VEHICLE_CONFIGURATION: TVC-F1
MISSION_PHASE: Pre-Launch
FLIGHT_ATTEMPT: Flights 1-3
OPEN_ITEM_STATUS: None
STATUS: Draft
STATEMENT: Demonstrate that the vehicle can clear the launch rail before beginning to actuate the gimbal.
RATIONALE: The rocket should not attempt to control itself until it has cleared the rail, as the rail is controlling the attitude at this point, and gimballing is likely to just cause more friction between the rail buttons and the rail.

[MISSION_RECORD]
UID: TVC-MC-004
RECORD_TYPE: Constraint
TITLE: Gound Kill Switch
SUBTEAM_OWNER: Software
INDIVIDUAL_OWNER: Software Lead
VEHICLE_CONFIGURATION: TVC-F1
MISSION_PHASE: Powered Ascent
FLIGHT_ATTEMPT: All
OPEN_ITEM_STATUS: None
STATUS: Draft
STATEMENT: The vehicle shall use a ground kill switch for the option of turning off controls from the ground.
RATIONALE: This constraint is required for introducing redundancy in killing the rocket controls, giving the ground team the ability to turn off controls if the rocket is visually considered to be in an unsafe state. The rocket concept of operations shall define more specific requirements for ground controls shutoff.
