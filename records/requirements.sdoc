[DOCUMENT]
TITLE: Requirements

[GRAMMAR]
IMPORT_FROM_FILE: @program

[REQUIREMENT]
UID: TVC-REQ-001
LEVEL: L1
REQUIREMENT_TYPE: Functional
TITLE: Ease of Integration
APPLICABLE_SUBSYSTEM: Airframe, Propulsion, Actuation, Recovery
SUBTEAM_OWNER: Systems, Structures, Electrical
INDIVIDUAL_OWNER: Systems Lead
VEHICLE_CONFIGURATION: TVC-F1
MISSION_PHASE: Pre-Launch
FLIGHT_ATTEMPT: All
OPEN_ITEM_STATUS: None
VERIFICATION_METHOD: Demonstration
VERIFICATION_PLAN_LINK: docs/verification/tvc-req-001.md
STATUS: Draft
STATEMENT: The vehicle shall be fully integrated, launched, and recovered within 2 hours under nominal conditions.
RATIONALE: This requirement decomposes TVC-MO-004, specifically focusing on the vehicle, and giving a specific timeframe for complete turnaround. Most launch sites are open from 10 AM to 4 PM, so 2 hours is the absolute maximum each launch may take. This does not take into account failures, which are varied and more specifically specified in the Concept of Operations documents.
RELATIONS:
- TYPE: Parent
  VALUE: TVC-MO-004

[REQUIREMENT]
UID: TVC-REQ-002
LEVEL: L1
REQUIREMENT_TYPE: Functional
TITLE: Flight Computer Fire Wire
APPLICABLE_SUBSYSTEM: Avionics, Recovery, Power
SUBTEAM_OWNER: Electrical
INDIVIDUAL_OWNER: Electrical Lead
VEHICLE_CONFIGURATION: TVC-F1
MISSION_PHASE: Parachute Descent
FLIGHT_ATTEMPT: All
OPEN_ITEM_STATUS: None
VERIFICATION_METHOD: Test
VERIFICATION_PLAN_LINK: docs/verification/tvc-req-002.md
STATUS: Draft
STATEMENT: The on board rocket avionics shall have the ability to set off fire wire, with at least 2 channels available to fire.
RATIONALE: This derived requirement ensures the rocket avionics will be able to support redundant single-deploy recovery.
RELATIONS:
- TYPE: Parent
  VALUE: TVC-MO-006

[REQUIREMENT]
UID: TVC-REQ-003
LEVEL: L1
REQUIREMENT_TYPE: Functional
TITLE: Flight Computer Data Logging
APPLICABLE_SUBSYSTEM: Avionics, Power, Flight_Software
SUBTEAM_OWNER: Electrical, Software
INDIVIDUAL_OWNER: Electrical Lead
VEHICLE_CONFIGURATION: TVC-F1
MISSION_PHASE: All
FLIGHT_ATTEMPT: All
OPEN_ITEM_STATUS: None
VERIFICATION_METHOD: Test
VERIFICATION_PLAN_LINK: docs/verification/tvc-req-003.md
STATUS: Draft
STATEMENT: The Flight Computer shall log all determined relevant flight data on an onboard SD-Card. This includes all raw sensor data (IMU, Barometer, other peripherals), relevant state estimation outputs (State Vector), actuator command outputs, individual control outputs, timestamps for each set of data, and current state of the state machine.
RATIONALE: This decomposes TVC-MO-005 to apply to flight computer onboard data logging, along with a more specific set of data to collect.
RELATIONS:
- TYPE: Parent
  VALUE: TVC-MO-005

[REQUIREMENT]
UID: TVC-REQ-004
LEVEL: L1
REQUIREMENT_TYPE: Functional
TITLE: Relevant Telemetry Data
APPLICABLE_SUBSYSTEM: Avionics, Power, Flight_Software, Ground_Systems
SUBTEAM_OWNER: Electrical, Software
INDIVIDUAL_OWNER: Electrical Lead
VEHICLE_CONFIGURATION: TVC-F1
MISSION_PHASE: All
FLIGHT_ATTEMPT: All
OPEN_ITEM_STATUS: None
VERIFICATION_METHOD: Test
VERIFICATION_PLAN_LINK: docs/verification/tvc-req-004.md
STATUS: Draft
STATEMENT: The flight computer shall send relevant flight data to a ground station via telemetry data packets. This includes state estimation outputs (State Vector), actuator commands outputs, individual control outputs, timestamps since launch, and the current state of the state machine.
RATIONALE: This decomposes TVC-MO-005 to apply to telemetry to the ground station, along with more specific information on what to send.
RELATIONS:
- TYPE: Parent
  VALUE: TVC-MO-005

[REQUIREMENT]
UID: TVC-REQ-005
LEVEL: L1
REQUIREMENT_TYPE: Performance
TITLE: Gimbal Minimum Angle (ARCHIVED, REFER TO TVC-REQ-060 FOR UPDATED GIMBAL REQUIREMENT)
APPLICABLE_SUBSYSTEM: Actuation
SUBTEAM_OWNER: Structures
INDIVIDUAL_OWNER: Structures Lead
VEHICLE_CONFIGURATION: TVC-F1
MISSION_PHASE: Powered Ascent
FLIGHT_ATTEMPT: Flight 1
OPEN_ITEM_STATUS: TBD
RESOLUTION_OWNER: Controls Lead
RESOLUTION_PLAN: Controls subteam will use a completed GNCSim architecture, with an integrated model/simulation of the gimbal, in order to determine the minimum gimbal angle. The simulation shall prove that the minimum gimbal angle (along with other gimbal properties) provided allows the rocket to maintain attitude under environmental conditions. Simulation results must be produced before the gimbal CDR. If GNCSim is not finished/integrated in time to complete this task, off the shelf tools such as aeroVECTOR will be used in replacement.
RESOLUTION_DUE_DATE: October 16th
VERIFICATION_METHOD: Demonstration
VERIFICATION_PLAN_LINK: docs/verification/tvc-req-005,6,7.md
STATUS: Draft
STATEMENT: The minimum actuation angle the gimbal shall be physically capable of is [TBD_GimAngle] degrees, in all directions (360 degrees).
RATIONALE: Based on results from GNCSim dynamic analysis, this will help establish the minimum ange the gimbal is capable of in order for the rocket to be physically capable of maintaining attitude, a fundamental function the rocket must have in order to meet system goals.
RELATIONS:
- TYPE: Parent
  VALUE: TVC-MO-001

[REQUIREMENT]
UID: TVC-REQ-006
LEVEL: L1
REQUIREMENT_TYPE: Performance
TITLE: Gimbal Minimum Velocity (ARCHIVED, REFER TO TVC-REQ-060 FOR UPDATED GIMBAL REQUIREMENT)
APPLICABLE_SUBSYSTEM: Actuation
SUBTEAM_OWNER: Structures
INDIVIDUAL_OWNER: Structures Lead
VEHICLE_CONFIGURATION: TVC-F1
MISSION_PHASE: Powered Ascent
FLIGHT_ATTEMPT: Flight 1
OPEN_ITEM_STATUS: TBD
RESOLUTION_OWNER: Controls Lead
RESOLUTION_PLAN: Controls subteam will use a completed GNCSim architecture, with an integrated model/simulation of the gimbal, in order to determine the minimum gimbal velocity. The simulation shall prove that the minimum gimbal velocity (along with other gimbal properties) provided allows the rocket to maintain attitude under environmental conditions. Simulation results must be produced before the gimbal CDR. If GNCSim is not finished/integrated in time to complete this task, off the shelf tools such as aeroVECTOR will be used in replacement.
RESOLUTION_DUE_DATE: October 16th
VERIFICATION_METHOD: Test
VERIFICATION_PLAN_LINK: docs/verification/tvc-req-005,6,7.md
STATUS: Draft
STATEMENT: The minimum velocity the gimbal shall be physically capable of is [TBD_GimVel] degrees/sec.
RATIONALE: Based on results from GNCSim dynamic analysis, this will help establish the minimum speed the gimbal is capable of in order for the rocket to be physically capable of maintaining attitude, a fundamental function the rocket must have to meet system goals.
RELATIONS:
- TYPE: Parent
  VALUE: TVC-MO-001

[REQUIREMENT]
UID: TVC-REQ-007
LEVEL: L1
REQUIREMENT_TYPE: Performance
TITLE: Gimbal Minimum Actuation Fidelity (ARCHIVED, REFER TO TVC-REQ-060 FOR UPDATED GIMBAL REQUIREMENT)
APPLICABLE_SUBSYSTEM: Actuation
SUBTEAM_OWNER: Structures
INDIVIDUAL_OWNER: Structures Lead
VEHICLE_CONFIGURATION: TVC-F1
MISSION_PHASE: Powered Ascent
FLIGHT_ATTEMPT: Flight 1
OPEN_ITEM_STATUS: TBD
RESOLUTION_OWNER: Controls Lead
RESOLUTION_PLAN: Controls subteam will use a completed GNCSim architecture, with an integrated model/simulation of the gimbal, in order to determine the minimum gimbal fidelity. The simulation shall prove that the minimum gimbal fidelity (along with other gimbal properties) provided allows the rocket to maintain attitude under environmental conditions. Simulation results must be produced before the gimbal CDR. If GNCSim is not finished/integrated in time to complete this task, off the shelf tools such as aeroVECTOR will be used in replacement.
RESOLUTION_DUE_DATE: October 16th
VERIFICATION_PLAN_LINK: docs/verification/tvc-req-005,6,7.md
VERIFICATION_METHOD: Test
STATUS: Draft
STATEMENT: The minimum actuation fidelity the gimbal shall be physically capable of is [TBD_TVCFid] degrees. This means the gimbal shall be able to actuate to positions that are multiples of the actuation fidelity.
RATIONALE: Based on results from GNCSim dynamic analysis, this will help establish the minimum actuation fidelity the gimbal is capable of in order for the rocket to be physically capable of maintaining attitude, a fundamental function the rocket must have to meet system goals.
RELATIONS:
- TYPE: Parent
  VALUE: TVC-MO-001

[REQUIREMENT]
UID: TVC-REQ-008
LEVEL: L2
REQUIREMENT_TYPE: Safety
TITLE: PCB Fire Wire Protection
APPLICABLE_SUBSYSTEM: Avionics
SUBTEAM_OWNER: Electrical
INDIVIDUAL_OWNER: Electrical Lead
VEHICLE_CONFIGURATION: TVC-F1
MISSION_PHASE: Pre-Launch
FLIGHT_ATTEMPT: All
OPEN_ITEM_STATUS: None
VERIFICATION_METHOD: Inspection
VERIFICATION_PLAN_LINK: docs/verification/tvc-req-008.md
STATUS: Draft
STATEMENT: The flight computer shall support a physical inhibit/enable switch for the fire wire, with physical on-board feedback of inhibit/enable status that the microcontroller can read.
RATIONALE: Inhibiting the fire wire switch is an important safety feature to ensure safe operations while handling the rocket up until launch operations. Feedback ensures the team is aware of the state of the fire wire.
RELATIONS:
- TYPE: Parent
  VALUE: TVC-REQ-002

[REQUIREMENT]
UID: TVC-REQ-009
LEVEL: L1
REQUIREMENT_TYPE: Design Constraint
TITLE: PCB Test Points
APPLICABLE_SUBSYSTEM: Avionics
SUBTEAM_OWNER: Electrical
INDIVIDUAL_OWNER: Electrical Lead
VEHICLE_CONFIGURATION: TVC-F1
MISSION_PHASE: All
FLIGHT_ATTEMPT: All
OPEN_ITEM_STATUS: None
VERIFICATION_METHOD: Inspection
VERIFICATION_PLAN_LINK: docs/verification/tvc-req-009.md
STATUS: Draft
STATEMENT: For major board circuitry, such as the recovery circuit, it shall be possible to physically check voltage using test points on the board. Important power lines, recovery circuitry, microcontroller debugging, interfaces (CAN, JTAG), and more shall include test points.
RATIONALE: This is both an important board design feature to allow for debugging in the case of failures during testing, and any last minute debugging required on the launch site.
RELATIONS:
- TYPE: Parent
  VALUE: TVC-MO-004

[REQUIREMENT]
UID: TVC-REQ-010
LEVEL: L1
REQUIREMENT_TYPE: Physical
TITLE: Flight Computer Accessibility
APPLICABLE_SUBSYSTEM: Avionics, Airframe
SUBTEAM_OWNER: Structures
INDIVIDUAL_OWNER: Structures Lead
VEHICLE_CONFIGURATION: TVC-F1
MISSION_PHASE: Pre-Launch
FLIGHT_ATTEMPT: All
OPEN_ITEM_STATUS: None
VERIFICATION_METHOD: Inspection
VERIFICATION_PLAN_LINK: docs/verification/tvc-req-010.md
STATUS: Draft
STATEMENT: For important flight computer debugging interfaces, such as flashing code and MCU reset, these interfaces shall be accessible during all pre-launch activities until the rocket is placed on the launch rail/pad.
RATIONALE: This requirement ensures rapid debugging in the case of failures, and gives the option for quick fixes without major rocket de-integration.
RELATIONS:
- TYPE: Parent
  VALUE: TVC-MO-004

[REQUIREMENT]
UID: TVC-REQ-011
LEVEL: L1
REQUIREMENT_TYPE: Interface
TITLE: Flight Computer Clearance
APPLICABLE_SUBSYSTEM: Avionics, Airframe
SUBTEAM_OWNER: Structures, Electrical
INDIVIDUAL_OWNER: Structures Lead
VEHICLE_CONFIGURATION: TVC-F1
MISSION_PHASE: Pre-Launch
FLIGHT_ATTEMPT: All
OPEN_ITEM_STATUS: None
VERIFICATION_METHOD: Analysis
VERIFICATION_PLAN_LINK: docs/verification/tvc-req-011.md
STATUS: Draft
STATEMENT: The avionics bay shall be able to fit all flight computer components in the body tube of the rocket, including any boards, wiring, connectors, power, antennas, etc...
RATIONALE: This requirement ensures spacing requirements for the flight computer will be met.
RELATIONS:
- TYPE: Parent
  VALUE: TVC-MO-007

[REQUIREMENT]
UID: TVC-REQ-012
LEVEL: L2
REQUIREMENT_TYPE: Interface
TITLE: Flight Computer Profile
APPLICABLE_SUBSYSTEM: Avionics, Airframe
SUBTEAM_OWNER: Structures, Electrical
INDIVIDUAL_OWNER: Electrical Lead
VEHICLE_CONFIGURATION: TVC-F1
MISSION_PHASE: All
FLIGHT_ATTEMPT: All
OPEN_ITEM_STATUS: None
VERIFICATION_METHOD: Inspection
VERIFICATION_PLAN_LINK: docs/verification/tvc-req-012.md
STATUS: Draft
STATEMENT: The flight computer stack bay shall match the max profile, when looking axially along the rocket, as shown in docs/Configuration/Flight Computer Stack Max Profile.png.
RATIONALE: This requirement decomposes TVC-REQ-010, giving an exact profile the flight computer stack (Collection of X boards) may maximally reach. The max profile was found using solidworks basic geometry.
RELATIONS:
- TYPE: Parent
  VALUE: TVC-REQ-010

[REQUIREMENT]
UID: TVC-REQ-013
LEVEL: L2
REQUIREMENT_TYPE: Interface
TITLE: Flight Computer Area
APPLICABLE_SUBSYSTEM: Avionics, Airframe
SUBTEAM_OWNER: Structures, Electrical
INDIVIDUAL_OWNER: Electrical Lead
VEHICLE_CONFIGURATION: TVC-F1
MISSION_PHASE: All
FLIGHT_ATTEMPT: All
OPEN_ITEM_STATUS: None
VERIFICATION_METHOD: Inspection
VERIFICATION_PLAN_LINK: docs/verification/tvc-req-013.md
STATUS: Draft
STATEMENT: The flight computer stack shall have a max footprint of 2.8 inches by 10 inches.
RATIONALE: 2.8 inches is the max width of the flight computer stack, found from solidworks. The length is constrained to 10 inches to prevent the rocket/avionics bay from lengthening too much, increasing mass.
RELATIONS:
- TYPE: Parent
  VALUE: TVC-REQ-010

[REQUIREMENT]
UID: TVC-REQ-014
LEVEL: L1
REQUIREMENT_TYPE: Physical
TITLE: Max Dry Rocket Mass
APPLICABLE_SUBSYSTEM: Airframe, Propulsion, Actuation, Avionics, Power, Recovery
SUBTEAM_OWNER: Structures, Electrical
INDIVIDUAL_OWNER: Systems Lead
VEHICLE_CONFIGURATION: TVC-F1
MISSION_PHASE: All
FLIGHT_ATTEMPT: All
OPEN_ITEM_STATUS: None
VERIFICATION_METHOD: Inspection
VERIFICATION_PLAN_LINK: docs/verification/tvc-req-014.md
STATUS: Draft
STATEMENT: The max dry mass of the rocket (mass without motors) shall be a maximum of 1050 grams.
RATIONALE: A simple, 1D simulation was put together in order to Validate this requirement. That simulation can be found in docs/Configuration/TVC-REQ-014 folder. This simple 1-D simulation is required, as OpenRocket cannot properly simulate the full flight of an unstable rocket. The mass of the rocket in the simulation was adjusted to find the absolute maximum mass that allowed for around 50 feet of altitude gain, with some tolerance. This ensures the rocket, assuming a mostly vertical flight, will not reach the ground before motor burnout.
RELATIONS:
- TYPE: Parent
  VALUE: TVC-MC-001

[REQUIREMENT]
UID: TVC-REQ-015
LEVEL: L2
REQUIREMENT_TYPE: Physical
TITLE: Max Gimbal Mass
APPLICABLE_SUBSYSTEM: Actuation
SUBTEAM_OWNER: Structures
INDIVIDUAL_OWNER: Structures Lead
VEHICLE_CONFIGURATION: TVC-F1
MISSION_PHASE: All
FLIGHT_ATTEMPT: All
OPEN_ITEM_STATUS: None
VERIFICATION_METHOD: Inspection
VERIFICATION_PLAN_LINK: docs/verification/tvc-req-015.md
STATUS: Draft
STATEMENT: The max mass of all gimbal components shall be a maximum of 350 grams.
RATIONALE: Using previous program experience. From Scarlet (Gimbaled 2024-2025) the mass of the gimbal was ~200 grams, but increased to ~800 grams on HPRTVC. Seeing as the architecture of Gimbaled TVC (Being low powered) matches Scarlet, but has greater restrictions (Accuracy, Speed, etc..) the mass is taken from Scarlet, with increased margin to allow for improved design. Evidence used: Scarlet OpenRocket (https://gtvault.sharepoint.com/:u:/s/gnc/IQDRCPbbADz0RYDQvH_F3RmwAXq7m1veWlWSwlan1esaDzY?e=n7STTH), HPRTVC masses (https://gtvault.sharepoint.com/:x:/s/gnc/IQCGeS3jqrzLSpojEPm9eAjLARGwMWSQHF-htBPefCFhMYI?e=eN0qTY)
RELATIONS:
- TYPE: Parent
  VALUE: TVC-REQ-014

[REQUIREMENT]
UID: TVC-REQ-016
LEVEL: L2
REQUIREMENT_TYPE: Physical
TITLE: Max Avionics Mass
APPLICABLE_SUBSYSTEM: Avionics, Power
SUBTEAM_OWNER: Structures
INDIVIDUAL_OWNER: Structures Lead
VEHICLE_CONFIGURATION: TVC-F1
MISSION_PHASE: All
FLIGHT_ATTEMPT: All
OPEN_ITEM_STATUS: None
VERIFICATION_METHOD: Inspection
VERIFICATION_PLAN_LINK: docs/verification/tvc-req-016.md
STATUS: Draft
STATEMENT: The max mass of all avionics components shall be a maximum of 350 grams.
RATIONALE: Using previous program experience. From Scarlet (Gimbaled 2024-2025) the mass of the avionics was ~500 grams, but increased to ~800 grams on HPRTVC. In order to accomodate other rocket changes, such as an improved gimbal, the mass budget for the avionics bay is slightly reduced. This is assumed to be practical, considering electrical team goals to make a lightweight, compact flight computer. Evidence used: Scarlet OpenRocket (https://gtvault.sharepoint.com/:u:/s/gnc/IQDRCPbbADz0RYDQvH_F3RmwAXq7m1veWlWSwlan1esaDzY?e=n7STTH), HPRTVC masses (https://gtvault.sharepoint.com/:x:/s/gnc/IQCGeS3jqrzLSpojEPm9eAjLARGwMWSQHF-htBPefCFhMYI?e=eN0qTY)
RELATIONS:
- TYPE: Parent
  VALUE: TVC-REQ-014

[REQUIREMENT]
UID: TVC-REQ-017
LEVEL: L2
REQUIREMENT_TYPE: Physical
TITLE: Max "other" mass
APPLICABLE_SUBSYSTEM: Airframe, Recovery
SUBTEAM_OWNER: Structures
INDIVIDUAL_OWNER: Structures Lead
VEHICLE_CONFIGURATION: TVC-F1
MISSION_PHASE: All
FLIGHT_ATTEMPT: All
OPEN_ITEM_STATUS: None
VERIFICATION_METHOD: Inspection
VERIFICATION_PLAN_LINK: docs/verification/tvc-req-017.md
STATUS: Draft
STATEMENT: The max mass of all non-gimbal, non-avionics components shall be a maximum of 350 grams. 
RATIONALE: Considering TVC-REQ-014 and TVC-REQ-015, the remaining mass in order to meet TVC-REQ-014 is 250g. 200g is set as the requirement to allow for a margin in the rocket mass (5%, but other components also include a margin).Seeing as the remaining mass includes airframe, nosecone, and recovery, this is likely a reasonable constraint, especially considering previous program experience.
RELATIONS:
- TYPE: Parent
  VALUE: TVC-REQ-014

[REQUIREMENT]
UID: TVC-REQ-018
LEVEL: L1
REQUIREMENT_TYPE: Functional
TITLE: Specific Controls Shutoff Conditions
APPLICABLE_SUBSYSTEM: Avionics, Flight_Software
SUBTEAM_OWNER: Controls
INDIVIDUAL_OWNER: Controls Lead
VEHICLE_CONFIGURATION: TVC-F1
MISSION_PHASE: Powered Ascent
FLIGHT_ATTEMPT: All
OPEN_ITEM_STATUS: TBD
RESOLUTION_OWNER: Controls Lead
RESOLUTION_PLAN: Once a completed GNCSim architecture has been put together, and the Gimbaled TVC rocket is ready to simulate, a variety of unsafe conditions should be simulated via Monte Carlo (Rocket Angle from Vertical, Angular rates in Pitch, Yaw, and Roll). For each of these factors, a maximum safe condition shall be decided, based on whether the rocket can recover from the condition by the end of the burn of the motor. Because the values are a small change in software, this can be resolved later on in the design cycle. Additionally, GNCSim should simulate what happens after controls shutoff. GNCSim should consider cases of return back to 0, return back to 0 and cut power, just cutting power, etc...
RESOLUTION_DUE_DATE: December 1st
VERIFICATION_METHOD: Test
VERIFICATION_PLAN_LINK: docs/verification/tvc-req-018.md
STATUS: Draft
STATEMENT: The rocket controls shall be turned off when unsafe conditions are reached. Unsafe conditions include: (1) Rocket [TBD_UnsafeDeg] degrees from vertical, (2) Rocket has [TBD_UnsafeRate] angular rate in Pitch/Yaw, (3) Rocket has [TBD_UnsafeRate2] angular rate in Roll. Controls shutoff sequence requires: 1- Actuating the gimbal to the known 0 position 2- Cutting power from the gimbal actuators.
RATIONALE: This meets the parent requirement, ensuring that controls are shutoff once angle, or rates, are too high to recover from. At this point, it is assumed the controls are not working as expected, and likely are contributing to rocket unsafe conditions. 
RELATIONS:
- TYPE: Parent
  VALUE: TVC-MO-008

[REQUIREMENT]
UID: TVC-REQ-019
LEVEL: L1
REQUIREMENT_TYPE: Design Constraint
TITLE: GNCSim for controls algorithm
APPLICABLE_SUBSYSTEM: Avionics, Flight_Software
SUBTEAM_OWNER: Controls
INDIVIDUAL_OWNER: Controls Lead
VEHICLE_CONFIGURATION: TVC-F1
MISSION_PHASE: All
FLIGHT_ATTEMPT: All
OPEN_ITEM_STATUS: None
VERIFICATION_METHOD: Inspection
VERIFICATION_PLAN_LINK: docs/verification/tvc-req-019.md
STATUS: Draft
STATEMENT: The controls team shall develop a full, closed-loop model of the Gimbaled TVC rocket in GNCSim in order find and tune the closed loop controls for the vehicle.
RATIONALE: In order to derive a control loop algorithm, the team shall use GNCSim to model the rocket, the control algorithm, and use GNCSim to evaluate the control algorithm (Stability, Response Time, Steady State Error, etc...)
RELATIONS:
- TYPE: Parent
  VALUE: TVC-MO-009

[REQUIREMENT]
UID: TVC-REQ-020
LEVEL: L2
REQUIREMENT_TYPE: Design Constraint
TITLE: GNCSim Modelling Inclusions
APPLICABLE_SUBSYSTEM: Avionics, Flight_Software
SUBTEAM_OWNER: Controls
INDIVIDUAL_OWNER: Controls Lead
VEHICLE_CONFIGURATION: TVC-F1
MISSION_PHASE: All
FLIGHT_ATTEMPT: All
OPEN_ITEM_STATUS: None
VERIFICATION_METHOD: Inspection
VERIFICATION_PLAN_LINK: docs/verification/tvc-req-020.md
STATUS: Draft
STATEMENT: GNCSim shall model multiple rocket elements, including but not limited to: Simple dynamics, Aerodynamics, Sensors, Actuator, Wind, etc...
RATIONALE: Modeling the above rocket elements will help ensure a complete rocket model and that all major factors affecting the rocket state/controls algorithm are accounted for. 
RELATIONS:
- TYPE: Parent
  VALUE: TVC-REQ-019

[REQUIREMENT]
UID: TVC-REQ-021
LEVEL: L2
REQUIREMENT_TYPE: Interface
TITLE: GNCSim Aerodynamics Requirements
APPLICABLE_SUBSYSTEM: Avionics, Flight_Software
SUBTEAM_OWNER: Aerodynamics
INDIVIDUAL_OWNER: Aerodynamics Lead
VEHICLE_CONFIGURATION: TVC-F1
MISSION_PHASE: All
FLIGHT_ATTEMPT: All
OPEN_ITEM_STATUS: None
VERIFICATION_METHOD: Inspection
VERIFICATION_PLAN_LINK: docs/verification/tvc-req-021.md
STATUS: Draft
STATEMENT: Aerodynamics shall provide a completed model of the aerodynamics characteristics of the rocket, in the form of a lookup table at various mach speeds and angles of attacks. These characteristics include but are not limited to: Cp location, Lift Coefficient, Drag Coefficient
RATIONALE: Modeling the above rocket elements will help ensure a complete rocket model and that all major factors affecting the rocket state/controls algorithm are accounted for. 
RELATIONS:
- TYPE: Parent
  VALUE: TVC-REQ-019

[REQUIREMENT]
UID: TVC-REQ-022
LEVEL: L1
REQUIREMENT_TYPE: Design Constraint
TITLE: Control Loop Overall Architecture
APPLICABLE_SUBSYSTEM: Avionics, Flight_Software
SUBTEAM_OWNER: Controls
INDIVIDUAL_OWNER: Controls Lead
VEHICLE_CONFIGURATION: TVC-F1
MISSION_PHASE: Powered Ascent
FLIGHT_ATTEMPT: All
OPEN_ITEM_STATUS: None
VERIFICATION_METHOD: Inspection
VERIFICATION_PLAN_LINK: docs/verification/tvc-req-022.md
STATUS: Draft
STATEMENT: The controls loop shall use a PID controller.
RATIONALE: PID control is the essential, basic controller, which is the best choice for a smaller rocket with a relatively basic goal. 
RELATIONS:
- TYPE: Parent
  VALUE: TVC-MO-009

[REQUIREMENT]
UID: TVC-REQ-023
LEVEL: L1
REQUIREMENT_TYPE: Design Constraint
TITLE: State Entry/Exit Criteria
APPLICABLE_SUBSYSTEM: Avionics, Flight_Software
SUBTEAM_OWNER: Software
INDIVIDUAL_OWNER: Software Lead
VEHICLE_CONFIGURATION: TVC-F1
MISSION_PHASE: All
FLIGHT_ATTEMPT: All
OPEN_ITEM_STATUS: TBR
RESOLUTION_OWNER: Software Lead
RESOLUTION_PLAN: Once state machine is more well defined, revesit the requirement and enforce specific state transitions based on TBR document that will outline each state transition and the conditions to make those transitions.
RESOLUTION_DUE_DATE: End of November
VERIFICATION_METHOD: Test
VERIFICATION_PLAN_LINK: docs/verification/tvc-req-023.md
STATUS: Draft
STATEMENT: Every state in the state machine shall have clearly defined entry and exit criteria, written in human English on the flight software github. Implementation of the entry and exit criteria shall demonstratably match what is written and prevent any invalid state transitions (Ex: Transitions to other states when unintended)
RATIONALE: Each state in a state machine must have a way to enter and exit. It is flight critical that the rocket does not enter a state when it is not intended for it to do so. For example, if the rocket were to enter the state pertaining to recovery prematurely, and prematurely deploy the parachute before motor burnout, that would be detrimental to the mission objectives.
RELATIONS:
- TYPE: Parent
  VALUE: TVC-MO-010

[REQUIREMENT]
UID: TVC-REQ-024
LEVEL: L1
REQUIREMENT_TYPE: Physical
TITLE: Motor Burn Time
APPLICABLE_SUBSYSTEM: Propulsion
SUBTEAM_OWNER: Systems
INDIVIDUAL_OWNER: Systems Lead
VEHICLE_CONFIGURATION: TVC-F1
MISSION_PHASE: Powered Ascent
FLIGHT_ATTEMPT: All
OPEN_ITEM_STATUS: None
VERIFICATION_METHOD: Inspection
VERIFICATION_PLAN_LINK: docs/verification/tvc-req-024.md
STATUS: Draft
STATEMENT: The motor shall have a burn time of at least 3 seconds.
RATIONALE: In order to demonstratably show the rocket controlling its attitude, it must have a long enough burn time to give the control system time to correct any errors in attitude. Assuming it takes the rocket ~1 second to clear the launch rail, a minimum of a three second burn time gives the rocket ~2 seconds to correct any errors in attitude. From previous program experience, the rocket has already reached a failed condition in less than a second once clearing the launch rail, so 2 seconds will be enough time to prove the rocket can stabilize and not reach a failed condition immediately.
RELATIONS:
- TYPE: Parent
  VALUE: TVC-MO-001

[REQUIREMENT]
UID: TVC-REQ-025
LEVEL: L2
REQUIREMENT_TYPE: Physical
TITLE: Gimbaled TVC Motor Selection
APPLICABLE_SUBSYSTEM: Propulsion
SUBTEAM_OWNER: Systems
INDIVIDUAL_OWNER: Systems Lead
VEHICLE_CONFIGURATION: TVC-F1
MISSION_PHASE: Powered Ascent
FLIGHT_ATTEMPT: Flight 1
OPEN_ITEM_STATUS: None
VERIFICATION_METHOD: Inspection
VERIFICATION_PLAN_LINK: docs/verification/tvc-req-025.md
STATUS: Draft
STATEMENT: The motor for Gimbaled TVC shall be the G12ST.
RATIONALE: The motor was chosen based off the Gimbaled TVC trade study, published in Notion under the Gimbaled TVC project docs (https://app.notion.com/p/LPRTVC-Motor-Trade-Study-3c5b2f334a1e804d9b0cca500c498f73?source=copy_link).
RELATIONS:
- TYPE: Parent
  VALUE: TVC-REQ-024

[REQUIREMENT]
UID: TVC-REQ-026
LEVEL: L1
REQUIREMENT_TYPE: Physical
TITLE: Constraining Motor in Gimbal
APPLICABLE_SUBSYSTEM: Propulsion
SUBTEAM_OWNER: Structures
INDIVIDUAL_OWNER: Structures Lead
VEHICLE_CONFIGURATION: TVC-F1
MISSION_PHASE: Pre-Launch
FLIGHT_ATTEMPT: Flight 1
OPEN_ITEM_STATUS: None
VERIFICATION_METHOD: Test
VERIFICATION_PLAN_LINK: docs/verification/tvc-req-026.md
STATUS: Draft
STATEMENT: The motor shall be properly constrained in the rocket, where it does not fall out under normal pre-launch activities, at all times from pre-launch to end of the mission.
RATIONALE: Constraining the motor is important to ensure flight operations go smoothly and the motor can properly transfer force to the vehicle.
RELATIONS:
- TYPE: Parent
  VALUE: TVC-MO-007

[REQUIREMENT]
UID: TVC-REQ-027
LEVEL: L1
REQUIREMENT_TYPE: Functional
TITLE: Parachute Release Conditions
APPLICABLE_SUBSYSTEM: Recovery, Flight_Software, Avionics
SUBTEAM_OWNER: Software
INDIVIDUAL_OWNER: Software Lead
VEHICLE_CONFIGURATION: TVC-F1
MISSION_PHASE: Parachute Descent
FLIGHT_ATTEMPT: All
OPEN_ITEM_STATUS: None
VERIFICATION_METHOD: Test
VERIFICATION_PLAN_LINK: docs/verification/tvc-req-027.md
STATUS: Draft
STATEMENT: The recovery system shall be deployed at the minimum expected velocity of the rocket (after the motor is fired), which is also apogee. Once the barometer data has no readings greater than a previous reading for >0.5 seconds, the fire wire should be set off.
RATIONALE: The parachute should be deployed at minumum velocity (apogee) to reduce loads on the chute and other recovery hardware. This condition can be most easily read by the barometer.
RELATIONS:
- TYPE: Parent
  VALUE: TVC-MO-006

[REQUIREMENT]
UID: TVC-REQ-028
LEVEL: L1
REQUIREMENT_TYPE: Design Constraint
TITLE: Rocket Airframe Material
APPLICABLE_SUBSYSTEM: Airframe
SUBTEAM_OWNER: Structures
INDIVIDUAL_OWNER: Structures Lead
VEHICLE_CONFIGURATION: TVC-F1
MISSION_PHASE: All
FLIGHT_ATTEMPT: All
OPEN_ITEM_STATUS: None
VERIFICATION_METHOD: Inspection
VERIFICATION_PLAN_LINK: docs/verification/tvc-req-028.md
STATUS: Draft
STATEMENT: The rocket shall use cardboard as the material for its airframe.
RATIONALE: Carboard is a lightweight material common for Low Power rockets. It is less dense than blue tube, and from previous program experience it is well equipped to experience the expected loads 
RELATIONS:
- TYPE: Parent
  VALUE: TVC-MO-007

[REQUIREMENT]
UID: TVC-REQ-029
LEVEL: L1
REQUIREMENT_TYPE: Design Constraint
TITLE: Rocket Airframe and Nosecone Material
APPLICABLE_SUBSYSTEM: Airframe
SUBTEAM_OWNER: Structures
INDIVIDUAL_OWNER: Structures Lead
VEHICLE_CONFIGURATION: TVC-F1
MISSION_PHASE: All
FLIGHT_ATTEMPT: All
OPEN_ITEM_STATUS: None
VERIFICATION_METHOD: Analysis
VERIFICATION_PLAN_LINK: docs/verification/tvc-req-029.md
STATUS: Draft
STATEMENT: The rocket shall use no metal in the cardboard airframe, in the nosecone, and any gimbal components that are not constrained in the body tube.
RATIONALE: NAR regulations do not allow metal in the externals of the rocket, this requirement decomposes the parent requirement to apply to specific components.
RELATIONS:
- TYPE: Parent
  VALUE: TVC-MC-002

[REQUIREMENT]
UID: TVC-REQ-030
LEVEL: L1
REQUIREMENT_TYPE: Safety
TITLE: Range Safety Constraints
APPLICABLE_SUBSYSTEM: N_A
SUBTEAM_OWNER: Controls
INDIVIDUAL_OWNER: Controls Lead
VEHICLE_CONFIGURATION: TVC-F1
MISSION_PHASE: All
FLIGHT_ATTEMPT: All
OPEN_ITEM_STATUS: TBD
RESOLUTION_OWNER: Controls Lead
RESOLUTION_PLAN: The requirement lists the resolution plan. GNCSim shall simulate the rocket dispersion under thrust to close this requirement.
RESOLUTION_DUE_DATE: September 30th, 2026
VERIFICATION_METHOD: Analysis
VERIFICATION_PLAN_LINK: docs/verification/tvc-req-030.md
STATUS: Draft
STATEMENT: The rocket launch range, [TBD_LaunchRange], shall be derived via Monte Carlo flight dynamic simulation. The vehicle's max TVC limit, aerodynamic load range, maximum determined failure modes should be considered. For range safety, altitude shall not be a consideration (At any range, the rocket is deemed unsafe, even if at a higher altitude)
RATIONALE: This requirement decomposes the parent requirement by specifically requiring dynamic analysis to find launch range, and setting specific constraints.
RELATIONS:
- TYPE: Parent
  VALUE: TVC-MC-003

[REQUIREMENT]
UID: TVC-REQ-031
LEVEL: L1
REQUIREMENT_TYPE: Safety
TITLE: Launch Rail Usage
APPLICABLE_SUBSYSTEM: Ground_Systems
SUBTEAM_OWNER: Structures
INDIVIDUAL_OWNER: Structures Lead
VEHICLE_CONFIGURATION: TVC-F1
MISSION_PHASE: All
FLIGHT_ATTEMPT: Flights 1-3
OPEN_ITEM_STATUS: None
VERIFICATION_METHOD: Demonstration
VERIFICATION_PLAN_LINK: docs/verification/tvc-req-031.md
STATUS: Draft
STATEMENT: The mission shall use a team-built launchpad that can be placed with no constraints anywhere on flat land. The launchpad shall be capable of standing upright with the rail attached, and allow for wireless ignition.
RATIONALE: This requirement ensures range safety will be met by allowing the rocket to be placed anywhere on the launch site. 
RELATIONS:
- TYPE: Parent
  VALUE: TVC-MC-003

[REQUIREMENT]
UID: TVC-REQ-032
LEVEL: L2
REQUIREMENT_TYPE: Safety
TITLE: Ground Ignition System
APPLICABLE_SUBSYSTEM: Ground_Systems
SUBTEAM_OWNER: Structures, Electrical, Software
INDIVIDUAL_OWNER: Electrical Lead
VEHICLE_CONFIGURATION: TVC-F1
MISSION_PHASE: All
FLIGHT_ATTEMPT: All
OPEN_ITEM_STATUS: TBR
RESOLUTION_OWNER: Electrical
RESOLUTION_PLAN: Once launch range has been established, the exact microcontroller and wireless communication method will be decided. For example, if launch range is expected to be over 300 feet, the Raspberry Pi wifi capabilities may not be sufficient.
RESOLUTION_DUE_DATE: October 31st, 2026
VERIFICATION_METHOD: Demonstration
VERIFICATION_PLAN_LINK: docs/verification/tvc-req-032.md
STATUS: Draft
STATEMENT: The team-built rocket ignition method shall use a Commerical off the shelf (COTS) micrcontroller (Such as Raspberry Pi), and use an e-match along with supporting components (Ex: Wiring). The micrcontroller shall have built in wireless communication capabilities or include a component (such as an external radio) that allows it to do so. The wireless communication method shall be: [TBD_WirelessCommMethod].
RATIONALE: Using a COTS microcontroller reduces complexity of the ground ignition system, and wireless communication is a must-have to allow the launch range to be met. The exact method of sending the ignition signal is TBD depending on how large the range actually is.
RELATIONS:
- TYPE: Parent
  VALUE: TVC-REQ-031

[REQUIREMENT]
UID: TVC-REQ-033
LEVEL: L1
REQUIREMENT_TYPE: Design Constraint
TITLE: Removable launch rail 
APPLICABLE_SUBSYSTEM: Ground_Systems
SUBTEAM_OWNER: Structures
INDIVIDUAL_OWNER: Structures Lead
VEHICLE_CONFIGURATION: TVC-F1
MISSION_PHASE: All
FLIGHT_ATTEMPT: All
OPEN_ITEM_STATUS: None
VERIFICATION_METHOD: Inspection
VERIFICATION_PLAN_LINK: docs/verification/tvc-req-033.md
STATUS: Draft
STATEMENT: The designed team-built launchpad shall have a removable launch rail.
RATIONALE: This ensures the team must only design/manufacture one launchpad, that is both applicable for launches with and without using a launch rail.
RELATIONS:
- TYPE: Parent
  VALUE: TVC-MO-011

[REQUIREMENT]
UID: TVC-REQ-034
LEVEL: L1
REQUIREMENT_TYPE: Physical
TITLE: Black Powder Used
APPLICABLE_SUBSYSTEM: Recovery
SUBTEAM_OWNER: Structures
INDIVIDUAL_OWNER: Structures Lead
VEHICLE_CONFIGURATION: TVC-F1
MISSION_PHASE: All
FLIGHT_ATTEMPT: All
OPEN_ITEM_STATUS: TBD
RESOLUTION_OWNER: Structures
RESOLUTION_PLAN: Black Powder testing, where the entire recovery system is placed in the rocket tube and black powder is ejected on the ground, will determine the sufficient amount of black powder.
RESOLUTION_DUE_DATE: October 30th, 2026
VERIFICATION_METHOD: Demonstration
VERIFICATION_PLAN_LINK: docs/verification/tvc-req-034.md
STATUS: Draft
STATEMENT: The rocket shall use a sufficient amount of black powder in order to effectively release the parachute system, [TBD_BlackPowder] grams at a minimum.
RATIONALE: An insufficient amount of black powder will lead to a stuck nosecone and a failure to effectively recover the rocket.
RELATIONS:
- TYPE: Parent
  VALUE: TVC-MO-006

[REQUIREMENT]
UID: TVC-REQ-035
LEVEL: L1
REQUIREMENT_TYPE: Design Constraint
TITLE: Recovery Electrical Independence
APPLICABLE_SUBSYSTEM: Recovery, Avionics
SUBTEAM_OWNER: Electrical
INDIVIDUAL_OWNER: Electrical Lead
VEHICLE_CONFIGURATION: TVC-F1
MISSION_PHASE: Parachute Descent
FLIGHT_ATTEMPT: All
OPEN_ITEM_STATUS: None
VERIFICATION_METHOD: Inspection
VERIFICATION_PLAN_LINK: docs/verification/tvc-req-035.md
STATUS: Draft
STATEMENT: The flight computer's recovery electrical power system shall operate independently from other board functions such as primariy flight control, using dedicated power rails and isolated distribution paths.
RATIONALE: Effective recovery means ensuring the fire wire is never set off accidentally. This is also a safety concern. Power system independence reduces the chance of a design error causing current/voltage surges.
RELATIONS:
- TYPE: Parent
  VALUE: TVC-MO-006

[REQUIREMENT]
UID: TVC-REQ-036
LEVEL: L1
REQUIREMENT_TYPE: Physical
TITLE: Recovery Parachute Sizing
APPLICABLE_SUBSYSTEM: Recovery
SUBTEAM_OWNER: Structures
INDIVIDUAL_OWNER: Structures Lead
VEHICLE_CONFIGURATION: TVC-F1
MISSION_PHASE: Parachute Descent
FLIGHT_ATTEMPT: All
OPEN_ITEM_STATUS: None
VERIFICATION_METHOD: Analysis
VERIFICATION_PLAN_LINK: docs/verification/tvc-req-036.md
STATUS: Draft
STATEMENT: The descent rate of the rocket shall be under 20 feet per second while under parachute.
RATIONALE: 20 feet per second is model rocketry standard parachute descent rate to ensure a safe recovery and low ground hit speed.
RELATIONS:
- TYPE: Parent
  VALUE: TVC-MO-006

[REQUIREMENT]
UID: TVC-REQ-037
LEVEL: L1
REQUIREMENT_TYPE: Physical
TITLE: Harness/Wiring Effective Routing
APPLICABLE_SUBSYSTEM: Airframe, Avionics, Actuation, Recovery
SUBTEAM_OWNER: Structures
INDIVIDUAL_OWNER: Structures Lead
VEHICLE_CONFIGURATION: TVC-F1
MISSION_PHASE: All
FLIGHT_ATTEMPT: All
OPEN_ITEM_STATUS: None
VERIFICATION_METHOD: Inspection
VERIFICATION_PLAN_LINK: docs/verification/tvc-req-037.md
STATUS: Draft
STATEMENT: All wiring in the rocket shall be tied off (mounted) at a maximum distance between ties of 0.75 inches.
RATIONALE: NASA STD-8739.4 gives standards for wire harnesses, and tells us that at a wire diameter of 0.25 inches or less, maximum tie off distance should be 0.75 inches. In the interest of a more conservative wiring plan, this standard is applied for all wire guages, not just the smallest given by NASA STD-8739.4.
RELATIONS:
- TYPE: Parent
  VALUE: TVC-MO-007

[REQUIREMENT]
UID: TVC-REQ-038
LEVEL: L1
REQUIREMENT_TYPE: Functional
TITLE: Launch State Transition
APPLICABLE_SUBSYSTEM: Avionics, Flight_Software
SUBTEAM_OWNER: Software
INDIVIDUAL_OWNER: Software Lead
VEHICLE_CONFIGURATION: TVC-F1
MISSION_PHASE: Pre-Launch
FLIGHT_ATTEMPT: All
OPEN_ITEM_STATUS: TBD
RESOLUTION_OWNER: Controls Lead
RESOLUTION_PLAN: in GNCSim, simulate the rocket launch. Ensure launch rail dynamics and sensor models are fully implemented. Over a Monte Carlo simulation find the largest and smallest average acceleration ~50ms immediately after launch. Use this to establish expected acceleration off the pad. Confirm with physical IMU whether normal noise will trigger this launch condition. If it will, increase time period.
RESOLUTION_DUE_DATE: September 30th
VERIFICATION_METHOD: Test
VERIFICATION_PLAN_LINK: docs/verification/tvc-req-038.md
STATUS: Draft
STATEMENT: The flight software shall detect launch, and once it does transition the state machine to powered ascent (Where active controls will be active). The conditions to detect launch shall be: Acceleration above [TBD_G_Value] for [TBD_Time] ms.
RATIONALE: This requirement decomposes the parent requirement by giving clear requirements for transition from the pre-launch state to the powered ascent state.
RELATIONS:
- TYPE: Parent
  VALUE: TVC-MO-010

[REQUIREMENT]
UID: TVC-REQ-039
LEVEL: L2
REQUIREMENT_TYPE: Performance
TITLE: Battery performance and life
APPLICABLE_SUBSYSTEM: Avionics, Power
SUBTEAM_OWNER: Electrical
INDIVIDUAL_OWNER: Electrical Lead
VEHICLE_CONFIGURATION: TVC-F1
MISSION_PHASE: Pre-Launch
FLIGHT_ATTEMPT: All
OPEN_ITEM_STATUS: None
VERIFICATION_METHOD: Analysis
VERIFICATION_PLAN_LINK: docs/verification/tvc-req-039.md
STATUS: Draft
STATEMENT: The vehicle battery shall last at least two hours under nominal expected operating conditions. Nominal operating conditions include power being on for 2 hours, with at least half an hour of actuation testing and other misc. testing and launch activities.
RATIONALE: In order to provide turnaround in two hours, it will be difficult to do so if having to replace the battery often. Ensuring the battery needs to be replaced, at a maximum, once between flights ensures there is no time wasted between launch turnaround time.
RELATIONS:
- TYPE: Parent
  VALUE: TVC-REQ-001

[REQUIREMENT]
UID: TVC-REQ-040
LEVEL: L1
REQUIREMENT_TYPE: Functional
TITLE: Overcurrent/Reverse Polarity Protections
APPLICABLE_SUBSYSTEM: Avionics, Power
SUBTEAM_OWNER: Electrical
INDIVIDUAL_OWNER: Electrical Lead
VEHICLE_CONFIGURATION: TVC-F1
MISSION_PHASE: Pre-Launch
FLIGHT_ATTEMPT: All
OPEN_ITEM_STATUS: None
VERIFICATION_METHOD: Demonstration
VERIFICATION_PLAN_LINK: docs/verification/tvc-req-040.md
STATUS: Draft
STATEMENT: The flight computer, and other supporting boards, shall have protection against overcurrent and reverse voltage. 
RATIONALE: A common club mistake has been plugging incorrect batteries/reversing battery connectors. To help prevent these mistakes crippling launch, boards must not be affected by incorrect power being plugged in.
RELATIONS:
- TYPE: Parent
  VALUE: TVC-MO-012

[REQUIREMENT]
UID: TVC-REQ-041
LEVEL: L1
REQUIREMENT_TYPE: Functional
TITLE: Labeling Wires Before Launch
APPLICABLE_SUBSYSTEM: Avionics, Power, Actuation
SUBTEAM_OWNER: Electrical
INDIVIDUAL_OWNER: Electrical Lead
VEHICLE_CONFIGURATION: TVC-F1
MISSION_PHASE: Pre-Launch
FLIGHT_ATTEMPT: All
OPEN_ITEM_STATUS: None
VERIFICATION_METHOD: Inspection
VERIFICATION_PLAN_LINK: docs/verification/tvc-req-041.md
STATUS: Draft
STATEMENT: Every single cable that is used for launch, ranging from servo cables for the actuators, to CAN connection, to JTAG connectors, shall be labeled before leaving for the launch site.
RATIONALE: Cables can be plugged in incorrectly, and labeling all of them beforehand gives time to double check connections beforehand and prevent on-site quick decisions from de-railing launches. This also helps improve turnaround as less time is spent deciding exactly which cables need to be plugged in where.
RELATIONS:
- TYPE: Parent
  VALUE: TVC-MO-012

[REQUIREMENT]
UID: TVC-REQ-042
LEVEL: L1
REQUIREMENT_TYPE: Design Constraint
TITLE: Gimbal Replaceable Motor Case
APPLICABLE_SUBSYSTEM: Propulsion, Actuation
SUBTEAM_OWNER: Structures
INDIVIDUAL_OWNER: Structures Lead
VEHICLE_CONFIGURATION: TVC-F1
MISSION_PHASE: Pre-Launch
FLIGHT_ATTEMPT: All
OPEN_ITEM_STATUS: None
VERIFICATION_METHOD: Demonstration
VERIFICATION_PLAN_LINK: docs/verification/tvc-req-042.md
STATUS: Draft
STATEMENT: The gimbal design shall use an easily replaceable motor holder.
RATIONALE: The motor holder, historically, has warped under heating from the motor. Instead of requiring the motor holder to be designed to handle the heat, this requirement allows warping, and replacing the motor in the engine is a motor of replacing the motor and holder as a unit.
RELATIONS:
- TYPE: Parent
  VALUE: TVC-MO-012

[REQUIREMENT]
UID: TVC-REQ-043
LEVEL: L1
REQUIREMENT_TYPE: Functional
TITLE: No last Minute Changes
APPLICABLE_SUBSYSTEM: N_A
SUBTEAM_OWNER: Systems
INDIVIDUAL_OWNER: Systems Lead
VEHICLE_CONFIGURATION: TVC-F1
MISSION_PHASE: Pre-Launch
FLIGHT_ATTEMPT: All
OPEN_ITEM_STATUS: None
VERIFICATION_METHOD: Inspection
VERIFICATION_PLAN_LINK: docs/verification/tvc-req-043.md
STATUS: Draft
STATEMENT: The rocket and supporting systems shall prevent any last minute changes made to the design, structures, flight software, avionics, etc... Note: Last minute is defined differently for different subsystems.
RATIONALE: Last minute changes are easy ways to introduce errors into the rocket. Last minute changes rarely can be tested, and if done quickly are more likely to contain mistakes. 
RELATIONS:
- TYPE: Parent
  VALUE: TVC-MO-012

[REQUIREMENT]
UID: TVC-REQ-044
LEVEL: L2
REQUIREMENT_TYPE: Functional
TITLE: Flight Software Changes
APPLICABLE_SUBSYSTEM: Flight_Software
SUBTEAM_OWNER: Software
INDIVIDUAL_OWNER: Software Lead
VEHICLE_CONFIGURATION: TVC-F1
MISSION_PHASE: Pre-Launch
FLIGHT_ATTEMPT: All
OPEN_ITEM_STATUS: None
VERIFICATION_METHOD: Inspection
VERIFICATION_PLAN_LINK: docs/verification/tvc-req-044.md
STATUS: Draft
STATEMENT: The flight software and supporting systems that the rocket will use shall prevent changes less than 0.5 weeks before the expected launch date. Tracking for flight software shall be done using github, and no commits from after the 0.5 week cutoff shall be used in the flight software for launch. For each version of flight software that is flown on a rocket, it must be tagged in Github with the flight number. (Tag: Flight #).
RATIONALE: This requirement decomposes the parent requirement to require a specific cutoff for changes to the flight software, along with requiring tags to improve traceability.
RELATIONS:
- TYPE: Parent
  VALUE: TVC-REQ-043

[REQUIREMENT]
UID: TVC-REQ-045
LEVEL: L1
REQUIREMENT_TYPE: Functional
TITLE: Flight Computer Controls Ability
APPLICABLE_SUBSYSTEM: Avionics, Flight_Software
SUBTEAM_OWNER: Electrical
INDIVIDUAL_OWNER: Electrical Lead
VEHICLE_CONFIGURATION: TVC-F1
MISSION_PHASE: Powered Ascent
FLIGHT_ATTEMPT: All
OPEN_ITEM_STATUS: TBD
RESOLUTION_OWNER: Controls
RESOLUTION_PLAN: Need to find required control loop update rate, Requirement TVC-REQ-047 lists the full completion plan to get this value.
RESOLUTION_DUE_DATE: Refer to TVC-REQ-047
VERIFICATION_METHOD: Test
VERIFICATION_PLAN_LINK: docs/verification/tvc-req-045.md
STATUS: Draft
STATEMENT: The flight computer shall be capable of running the controls algorithm at the required rate (Refer to TVC-REQ-047). It must also include all required minimum sensors and be able to read sensor data. Minimum sensors: IMU, Barometer
RATIONALE: In order to run on-board controls, the flight computer must do so. It shall not be a limiting factor for the control loop rate. The flight computer also must have the required sensors to do GNC.
RELATIONS:
- TYPE: Parent
  VALUE: TVC-MO-009

[REQUIREMENT]
UID: TVC-REQ-046
LEVEL: L1
REQUIREMENT_TYPE: Functional
TITLE: Flight Computer TVC Ability
APPLICABLE_SUBSYSTEM: Avionics, Flight_Software, Actuation
SUBTEAM_OWNER: Electrical
INDIVIDUAL_OWNER: Electrical Lead
VEHICLE_CONFIGURATION: TVC-F1
MISSION_PHASE: Powered Ascent
FLIGHT_ATTEMPT: All
OPEN_ITEM_STATUS: TBR
RESOLUTION_OWNER: Controls lead
RESOLUTION_PLAN: Once controls has resolved the minimum Gimbal Velocity, this help establish how quickly the update rate of the gimbal must be. Refer to TVC-REQ-006 for a more detailed resolution plan.
RESOLUTION_DUE_DATE: Refer to TVC-REQ-006
VERIFICATION_METHOD: Test
VERIFICATION_PLAN_LINK: docs/verification/tvc-req-046.md
STATUS: Draft
STATEMENT: The flight computer shall be capable of controlling the actuators for the gimbal. It shall be able to send commands in order to meet minimum requirements for speed of the gimbal (TVC-REQ-006), [TBD_GimbalVelocity]
RATIONALE: The flight computer must be able to control the gimbal to allow for effective closed loop on-board controls.
RELATIONS:
- TYPE: Parent
  VALUE: TVC-MO-009

[REQUIREMENT]
UID: TVC-REQ-047
LEVEL: L1
REQUIREMENT_TYPE: Performance
TITLE: Flight loop update rate
APPLICABLE_SUBSYSTEM: Avionics, Flight_Software
SUBTEAM_OWNER: Software
INDIVIDUAL_OWNER: Software Lead
VEHICLE_CONFIGURATION: TVC-F1
MISSION_PHASE: Powered Ascent
FLIGHT_ATTEMPT: All
OPEN_ITEM_STATUS: TBD
RESOLUTION_OWNER: Controls Lead
RESOLUTION_PLAN: Need to consider Nyquist Criterion, etc... in order to decide proper update rate to allow for a controller that updates quickly enough to ensure closed loop controls can be achieved.
RESOLUTION_DUE_DATE: September 18
VERIFICATION_METHOD: Demonstration
VERIFICATION_PLAN_LINK: docs/verification/tvc-req-047.md
STATUS: Draft
STATEMENT: The flight software loop shall run at a minimum of [TBD_UpdateRate] Hz and a maximum of 333 Hz.
RATIONALE: Need to have a minumum control loop run in order to ensure the TVC is reacting quickly enough. That being said, the servos have a command frequency (recommended) for 333 Hz, and this sets an upper limit for the update rate of the flight loop.
RELATIONS:
- TYPE: Parent
  VALUE: TVC-MO-009

[REQUIREMENT]
UID: TVC-REQ-048
LEVEL: L2
REQUIREMENT_TYPE: Performance
TITLE: Sensor Update Rate
APPLICABLE_SUBSYSTEM: Avionics, Flight_Software
SUBTEAM_OWNER: Software, Electrical
INDIVIDUAL_OWNER: Software Lead
VEHICLE_CONFIGURATION: TVC-F1
MISSION_PHASE: Powered Ascent
FLIGHT_ATTEMPT: All
OPEN_ITEM_STATUS: TBD
RESOLUTION_OWNER: Controls
RESOLUTION_PLAN: Need to find required control loop update rate, Requirement TVC-REQ-047 lists the full completion plan to get this value.
RESOLUTION_DUE_DATE: Refer to TVC-REQ-047
VERIFICATION_METHOD: Demonstration
VERIFICATION_PLAN_LINK: docs/verification/tvc-req-048.md
STATUS: Draft
STATEMENT: All sensors shall have a minimum update rate of [TBD_UpdateRate] Hz.
RATIONALE: Controls requires a minimum update rate of the control loop, and the controllers must follow this update rate to support this control loop rate.
RELATIONS:
- TYPE: Parent
  VALUE: TVC-REQ-046

[REQUIREMENT]
UID: TVC-REQ-049
LEVEL: L1
REQUIREMENT_TYPE: Functional
TITLE: Kalman Filter Usage
APPLICABLE_SUBSYSTEM: Avionics, Flight_Software
SUBTEAM_OWNER: Software, Controls
INDIVIDUAL_OWNER: Software Lead
VEHICLE_CONFIGURATION: TVC-F1
MISSION_PHASE: Powered Ascent
FLIGHT_ATTEMPT: All
OPEN_ITEM_STATUS: TBD
RESOLUTION_OWNER: Controls Lead
RESOLUTION_PLAN: Once system has been more well defined, especially sensors, use sensor datasheets/noise information to decide RMS.
RESOLUTION_DUE_DATE: End of November
VERIFICATION_METHOD: Demonstration
VERIFICATION_PLAN_LINK: docs/verification/tvc-req-049.md
STATUS: Draft
STATEMENT: The flight software shall implement a Kalman filter for state estimation. The Kalman filter shall have P matrix covariance less than Q and R, and an RMS less than TBD.
RATIONALE: Kalman filter is an industry standard method of improving the accuracy of state estimation, which will improve the quality of the rocket closed loop controls.
RELATIONS:
- TYPE: Parent
  VALUE: TVC-MO-009

[REQUIREMENT]
UID: TVC-REQ-050
LEVEL: L1
REQUIREMENT_TYPE: Performance
TITLE: Flight Algorithm Stability
APPLICABLE_SUBSYSTEM: Avionics, Flight_Software
SUBTEAM_OWNER: Controls
INDIVIDUAL_OWNER: Controls Lead
VEHICLE_CONFIGURATION: TVC-F1
MISSION_PHASE: Powered Ascent
FLIGHT_ATTEMPT: All
OPEN_ITEM_STATUS: None
VERIFICATION_METHOD: Analysis
VERIFICATION_PLAN_LINK: docs/verification/tvc-req-050.md
STATUS: Draft
STATEMENT: The controls algorithm shall be demonstratably stable over the course of the rocket's flight, within the expected controls range (Max angle of attack before controls is turned off). Demonstration of stability should include a demonstration of stability in the S-Plane, along with simulation data showing the rocket has a bounded output in response to defined mission disturbances (From TVC-MO-002 and decomposed requirements).
RATIONALE: In order to effectively stabilize the rocket, the flight algorithm must be stable over the course of the flight. Oscillations, exponential increases, etc... are all indicative of non-stable controls algorithm.
RELATIONS:
- TYPE: Parent
  VALUE: TVC-MO-001

[REQUIREMENT]
UID: TVC-REQ-051
LEVEL: L1
REQUIREMENT_TYPE: Functional
TITLE: Controls algorithm delay
APPLICABLE_SUBSYSTEM: Avionics, Flight_Software
SUBTEAM_OWNER: Software, Controls
INDIVIDUAL_OWNER: Software Lead
VEHICLE_CONFIGURATION: TVC-F1
MISSION_PHASE: Powered Ascent
FLIGHT_ATTEMPT: Flights 1-3
OPEN_ITEM_STATUS: TBR
RESOLUTION_OWNER: Structures
RESOLUTION_PLAN: Waiting for a decision on launch rail height. Once rail height has been found, need to research how to simulate launch rail friction/loads for rocket, to find how long it would take the rocket to clear the rail. 
RESOLUTION_DUE_DATE: November 30th
VERIFICATION_METHOD: Demonstration
VERIFICATION_PLAN_LINK: docs/verification/tvc-req-051.md
STATUS: Draft
STATEMENT: The controls algorithm shall be delayed by [TBD_DelaySeconds] after launch is detected, before active controls are activated. This delay shall be baked into the powered ascent state.
RATIONALE: Need to set a specific delay before the rocket begins controlling the gimbal, in order for the rocket to clear the rail before starting active controls. Use rail length to determine the length.
RELATIONS:
- TYPE: Parent
  VALUE: TVC-MO-013

[REQUIREMENT]
UID: TVC-REQ-052
LEVEL: L1
REQUIREMENT_TYPE: Performance
TITLE: Wind Response Capability
APPLICABLE_SUBSYSTEM: Avionics, Flight_Software, Actuation
SUBTEAM_OWNER: Software, Controls, Structures
INDIVIDUAL_OWNER: Controls Lead
VEHICLE_CONFIGURATION: TVC-F1
MISSION_PHASE: Powered Ascent
FLIGHT_ATTEMPT: All
OPEN_ITEM_STATUS: None
VERIFICATION_METHOD: Analysis
VERIFICATION_PLAN_LINK: docs/verification/tvc-req-052.md
STATUS: Draft
STATEMENT: The rocket shall be able to maintain vertical attitude under conditions of 10 MPH wind.
RATIONALE: The average wind speed in Samson Alabama, one of the launch sites GNC uses, has around a max wind speed of 10 MPH during the year. Samson is more coastal compared to other launch sites, meaning it has higher winds (as coastal areas usually do). Therefore, this requirement reflects a worst case environmental conditions for the rocket.
RELATIONS:
- TYPE: Parent
  VALUE: TVC-MO-002

[REQUIREMENT]
UID: TVC-REQ-053
LEVEL: L1
REQUIREMENT_TYPE: Performance
TITLE: Rocket Temperature Operating Range
APPLICABLE_SUBSYSTEM: Avionics, Actuation, Power, Ground_Systems
SUBTEAM_OWNER: Systems
INDIVIDUAL_OWNER: Systems Lead
VEHICLE_CONFIGURATION: TVC-F1
MISSION_PHASE: Powered Ascent
FLIGHT_ATTEMPT: All
OPEN_ITEM_STATUS: None
VERIFICATION_METHOD: Test
VERIFICATION_PLAN_LINK: docs/verification/tvc-req-053.md
STATUS: Draft
STATEMENT: The rocket shall operate in a temperature range of 40 Deg F to 100 deg F.
RATIONALE: For Samson Alabama, the average low in the coldest month (January) is around 42 degrees F, and the average high in the hottest month (July) is around 91 degrees F. This requirement gives a tolerance for highest and lowest temperature. It is assumed that the team will not attend a launch if the temperature dips below 40 degrees.
RELATIONS:
- TYPE: Parent
  VALUE: TVC-MO-002

[REQUIREMENT]
UID: TVC-REQ-054
LEVEL: L1
REQUIREMENT_TYPE: Functional
TITLE: Controls Shutoff From Ground Station
APPLICABLE_SUBSYSTEM: Ground_Systems
SUBTEAM_OWNER: Software
INDIVIDUAL_OWNER: Software Lead
VEHICLE_CONFIGURATION: TVC-F1
MISSION_PHASE: Powered Ascent
FLIGHT_ATTEMPT: All
OPEN_ITEM_STATUS: None
VERIFICATION_METHOD: Test
VERIFICATION_PLAN_LINK: docs/verification/tvc-req-054.md
STATUS: Draft
STATEMENT: The ground station UI shall include an option to manually shutoff controls on the rocket and provide feedback on whether the rocket successfully does so or not. Controls shutoff sequence requires: 1- Actuating the gimbal to the known 0 position 2- Cutting power from the gimbal actuators.
RATIONALE: This decomposes the parent requirement, specifically stating the function of the ground station and what turning off controls actually requires.
RELATIONS:
- TYPE: Parent
  VALUE: TVC-MC-004

[REQUIREMENT]
UID: TVC-REQ-055
LEVEL: L2
REQUIREMENT_TYPE: Functional
TITLE: Controls Shutoff Package Receive
APPLICABLE_SUBSYSTEM: Ground_Systems
SUBTEAM_OWNER: Software
INDIVIDUAL_OWNER: Software Lead
VEHICLE_CONFIGURATION: TVC-F1
MISSION_PHASE: Powered Ascent
FLIGHT_ATTEMPT: All
OPEN_ITEM_STATUS: None
VERIFICATION_METHOD: Test
VERIFICATION_PLAN_LINK: docs/verification/tvc-req-055.md
STATUS: Draft
STATEMENT: The ground station shall continue to send packages with controls shutoff command until it recieves a return package with confirmation of a controls shutoff. The flight software shall include the capability to recieve the controls shutoff commands, go through the sequence defined in TVC-REQ-054, then return a confirmation package only once the sequence is complete.
RATIONALE: This requirement improves the likelihood of controls shutoff actually occuring once the user commands so, forcing the command to be sent until there is confirmation it has occured. This requirement also ensures that small cutouts in radio signal do not prevent controls shutoff from occuring.
RELATIONS:
- TYPE: Parent
  VALUE: TVC-REQ-054

[REQUIREMENT]
UID: TVC-REQ-056
LEVEL: L2
REQUIREMENT_TYPE: Safety
TITLE: Remote Ignition Inhibit
APPLICABLE_SUBSYSTEM: Ground_Systems
SUBTEAM_OWNER: Electrical
INDIVIDUAL_OWNER: Electrical Lead
VEHICLE_CONFIGURATION: TVC-F1
MISSION_PHASE: Pre-Launch
FLIGHT_ATTEMPT: All
OPEN_ITEM_STATUS: None
VERIFICATION_METHOD: Test
VERIFICATION_PLAN_LINK: docs/verification/tvc-req-056.md
STATUS: Draft
STATEMENT: The remote ignition hardware shall have a physical inhibit switch that prevents stray RF signals from accidentally initializing the ignition sequence.
RATIONALE: For any ignition, black powder, fire wire, etc... it is common GNC practice to have a physical inhibit switch. In this case, the inhibit switch both ensures that the ignition does not go off when there are unsafe conditions (Ex: Personnel near it), or when the team is not ready for the rocket to launch (Ex: High Wind)
RELATIONS:
- TYPE: Parent
  VALUE: TVC-REQ-031

[REQUIREMENT]
UID: TVC-REQ-057
LEVEL: L1
REQUIREMENT_TYPE: Functional
TITLE: Number of Cameras at launch
APPLICABLE_SUBSYSTEM: Ground_Systems
SUBTEAM_OWNER: Systems
INDIVIDUAL_OWNER: Systems Lead
VEHICLE_CONFIGURATION: TVC-F1
MISSION_PHASE: All
FLIGHT_ATTEMPT: All
OPEN_ITEM_STATUS: None
VERIFICATION_METHOD: Inspection
VERIFICATION_PLAN_LINK: docs/verification/tvc-req-057.md
STATUS: Draft
STATEMENT: The rocket launch shall have at least three cameras on the ground that are pointed towards the rocket, and will film each rocket flight. At least one shall have thermal protection so that it can be placed near the rocket, and at least one shall be held by a person so that they can film the entire rocket flight.
RATIONALE: This decomposes the parent requirement into a specific number of cameras and configurations of them.
RELATIONS:
- TYPE: Parent
  VALUE: TVC-MO-003

[REQUIREMENT]
UID: TVC-REQ-058
LEVEL: L1
REQUIREMENT_TYPE: Functional
TITLE: Pre-Launch Photos
APPLICABLE_SUBSYSTEM: Ground_Systems
SUBTEAM_OWNER: Systems
INDIVIDUAL_OWNER: Systems Lead
VEHICLE_CONFIGURATION: TVC-F1
MISSION_PHASE: All
FLIGHT_ATTEMPT: All
OPEN_ITEM_STATUS: None
VERIFICATION_METHOD: Inspection
VERIFICATION_PLAN_LINK: docs/verification/tvc-req-058.md
STATUS: Draft
STATEMENT: Before going to the launch site, GNC shall take high quality, PR-ready photos of each and every subsystem of note, including but not limited to: Gimbal, Flight Computer, Ground Station. There shall also be high quality simulation photos from the development cycle, including but not limited to: CFD, Dynamic Visualizations
RATIONALE: This decomposes and extends the parent requirement to apply not just to launch, but also to the development cycle of the rocket and all the important subsytems that go into development.
RELATIONS:
- TYPE: Parent
  VALUE: TVC-MO-003

[REQUIREMENT]
UID: TVC-REQ-059
LEVEL: L2
REQUIREMENT_TYPE: Functional
TITLE: Controls Changes Cutoff
APPLICABLE_SUBSYSTEM: Flight_Software
SUBTEAM_OWNER: Systems
INDIVIDUAL_OWNER: Systems Lead
VEHICLE_CONFIGURATION: TVC-F1
MISSION_PHASE: All
FLIGHT_ATTEMPT: Flight 1
OPEN_ITEM_STATUS: None
VERIFICATION_METHOD: Inspection
VERIFICATION_PLAN_LINK: docs/verification/tvc-req-059.md
STATUS: Draft
STATEMENT: Controls shall have a change cutoff of 0.5 weeks before launch, but after the first launch of the day the control gains shall not be controlled.
RATIONALE: This ensures no last minute detrimental change to gains, but still allows the team to change the controller after the fact.
RELATIONS:
- TYPE: Parent
  VALUE: TVC-REQ-043

[REQUIREMENT]
UID: TVC-REQ-060
LEVEL: L1
REQUIREMENT_TYPE: Performance
TITLE: Controls Algorithm Gimbal Performance
APPLICABLE_SUBSYSTEM: Flight_Software
SUBTEAM_OWNER: Controls
INDIVIDUAL_OWNER: Controls Lead
VEHICLE_CONFIGURATION: TVC-F1
MISSION_PHASE: All
FLIGHT_ATTEMPT: Flight 1
OPEN_ITEM_STATUS: None
VERIFICATION_METHOD: Inspection
VERIFICATION_PLAN_LINK: docs/verification/tvc-req-060.md
STATUS: Draft
STATEMENT: The controls algorithm shall accurately model the gimbal and, through simulation, demonstratably be able to control the attitude of the rocket under nominal and environmental conditions outlined in TVC-MO-002.
RATIONALE: The gimbal does not have any strict requirements, so this requirement applies to the control algorithm being able to control the rocket, based on the gimbal that is created. 
RELATIONS:
- TYPE: Parent
  VALUE: TVC-MO-001

[REQUIREMENT]
UID: TVC-REQ-061
LEVEL: L2
REQUIREMENT_TYPE: Performance
TITLE: Gimbal Required Modeling
APPLICABLE_SUBSYSTEM: Actuation
SUBTEAM_OWNER: Structures
INDIVIDUAL_OWNER: Structures Lead
VEHICLE_CONFIGURATION: TVC-F1
MISSION_PHASE: All
FLIGHT_ATTEMPT: Flight 1
OPEN_ITEM_STATUS: None
VERIFICATION_METHOD: Inspection
VERIFICATION_PLAN_LINK: docs/verification/tvc-req-061.md
STATUS: Draft
STATEMENT: The gimbal's position shall be modeled, with servo position and speed as the input to the model. The gimbal's position is what is modeled.
RATIONALE: In order to accurately model the gimbal and demonstrate rocket controllability, controls needs a model of the gimbal, which structures must complete. 
RELATIONS:
- TYPE: Parent
  VALUE: TVC-REQ-060

[REQUIREMENT]
UID: TVC-REQ-062
LEVEL: L2
REQUIREMENT_TYPE: Performance
TITLE: Servo Required Modeling
APPLICABLE_SUBSYSTEM: Actuation
SUBTEAM_OWNER: Structures
INDIVIDUAL_OWNER: Structures Lead
VEHICLE_CONFIGURATION: TVC-F1
MISSION_PHASE: All
FLIGHT_ATTEMPT: Flight 1
OPEN_ITEM_STATUS: None
VERIFICATION_METHOD: Inspection
VERIFICATION_PLAN_LINK: docs/verification/tvc-req-062.md
STATUS: Draft
STATEMENT: The servo shall be modeled via physical ID (Using an encoder), where position and speed data is collected to build a model of the servo. Loading conditions shall be considered.
RATIONALE: In order to accurately model the gimbal, an ID needs to be done on the servo we will be using. Speed and position will be used as inputs for the gimbal model.
RELATIONS:
- TYPE: Parent
  VALUE: TVC-REQ-060
